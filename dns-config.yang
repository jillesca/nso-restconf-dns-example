module dns-config {

  namespace "http://example.com/dns-config";
  prefix dns-config;
  
  import ietf-inet-types {
    prefix inet;
  }
  import tailf-ncs {
    prefix ncs;
  }

  container dns {
    list server {
      key "address";
      max-elements "3";
      ordered-by user;

      uses ncs:service-data;
      ncs:servicepoint dns-config-servicepoint;

      leaf address {
        type inet:ipv4-address;
      }

      leaf-list device {
        type leafref {
          path "/ncs:devices/ncs:device/ncs:name";
        }
      }
      
    }
  }
}
